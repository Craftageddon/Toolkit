;;; Craftageddon restricted 2D import. Review before APPLOAD. Millimeter drawing ONLY.
;;; Generated data: 4 entities. Command: CFIMPORT (not auto executed).
(defun c:CFIMPORT (/ errors oldunits)
  (setq errors 0)
  (setq oldunits (getvar "INSUNITS"))
  (if (/= oldunits 4)
    (princ "\nWARNING: Drawing INSUNITS is not millimeters. No changes made; set to mm manually.")
    (progn
      (if (not (tblsearch "LAYER" "CG_CUT"))
        (if (not (entmake (list (cons 0 "LAYER") (cons 100 "AcDbSymbolTableRecord") (cons 100 "AcDbLayerTableRecord") (cons 2 "CG_CUT") (cons 70 0) (cons 62 1) (cons 6 "Continuous")))) (setq errors (+ errors 1)))
        (if (or (/= (abs (cdr (assoc 62 (tblsearch "LAYER" "CG_CUT")))) 1)
                (assoc 420 (tblsearch "LAYER" "CG_CUT")))
          (setq errors (+ errors 1))))
      (if (not (tblsearch "LAYER" "CG_HOLES"))
        (if (not (entmake (list (cons 0 "LAYER") (cons 100 "AcDbSymbolTableRecord") (cons 100 "AcDbLayerTableRecord") (cons 2 "CG_HOLES") (cons 70 0) (cons 62 1) (cons 6 "Continuous")))) (setq errors (+ errors 1)))
        (if (or (/= (abs (cdr (assoc 62 (tblsearch "LAYER" "CG_HOLES")))) 1)
                (assoc 420 (tblsearch "LAYER" "CG_HOLES")))
          (setq errors (+ errors 1))))
      (if (not (tblsearch "LAYER" "CG_REFERENCE"))
        (if (not (entmake (list (cons 0 "LAYER") (cons 100 "AcDbSymbolTableRecord") (cons 100 "AcDbLayerTableRecord") (cons 2 "CG_REFERENCE") (cons 70 0) (cons 62 4) (cons 6 "Continuous")))) (setq errors (+ errors 1)))
        (if (or (/= (abs (cdr (assoc 62 (tblsearch "LAYER" "CG_REFERENCE")))) 4)
                (assoc 420 (tblsearch "LAYER" "CG_REFERENCE")))
          (setq errors (+ errors 1))))
      (if (= errors 0)
        (progn
  (if (not (entmake (list (cons 0 "LWPOLYLINE") (cons 100 "AcDbEntity") (cons 8 "CG_CUT") (cons 100 "AcDbPolyline") (cons 90 4) (cons 70 1)
    (cons 10 (list 0.0 0.0))
    (cons 10 (list 80.0 0.0))
    (cons 10 (list 80.0 50.0))
    (cons 10 (list 0.0 50.0))))) (setq errors (+ errors 1)))
  (if (not (entmake (list (cons 0 "CIRCLE") (cons 8 "CG_HOLES") (cons 10 (list 10.0 10.0 0.0)) (cons 40 2.0)))) (setq errors (+ errors 1)))
  (if (not (entmake (list (cons 0 "CIRCLE") (cons 8 "CG_HOLES") (cons 10 (list 70.0 10.0 0.0)) (cons 40 2.0)))) (setq errors (+ errors 1)))
  (if (not (entmake (list (cons 0 "LINE") (cons 8 "CG_REFERENCE") (cons 10 (list 40.0 0.0 0.0)) (cons 11 (list 40.0 50.0 0.0))))) (setq errors (+ errors 1)))
          (if (= errors 0) (princ "\nCFIMPORT completed.") (princ (strcat "\nCFIMPORT entity errors: " (itoa errors))))
        )
        (princ "\nCFIMPORT stopped: expected CUT/HOLES red and REFERENCE cyan layers could not be created or colors conflict.")
      )
    )
  )
  (princ)
)
(princ "\nCFIMPORT loaded. Type CFIMPORT in a disposable mm drawing to run.")
(princ)
